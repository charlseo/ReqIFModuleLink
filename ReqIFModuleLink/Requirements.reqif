# IBM Rational Requirements Wed Jan 25 12:15:15 EST 2017

# Specification: Family 1 - Spec Module
- ReqIF.Name: Family 1 - Spec Module
- Artifact Format: Module

## 1287: Cook's Family Tree (Heading)
- Artifact Format: Text

### 1596: Granpa Cook (Technical Requirement)
- Artifact Format: Text

### 1858: Mother Cook Update from Downer (Technical Requirement)
- Artifact Format: Text

### 1323: Father Cook (Technical Requirement)
- Artifact Format: Text

### 2206: Father Smith (Technical Requirement)
- Artifact Format: Text

### 1327: Child 1 Cook (Technical Requirement)
- Artifact Format: Text
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
### 1710: Child 2 Cook (Technical Requirement)
Child 2 Cook test
- Artifact Format: Text
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